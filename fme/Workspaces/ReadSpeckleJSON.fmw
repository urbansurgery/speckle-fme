FME workspace ReadSpeckleJSON.fmw

Parameters:
- FILEPATH_OR_URL =

Creator
    GEOMTYPE = Geometry Object
    NUM = 1
    CREATED -> JSONFragmenter
Note: Read Speckle JSON and fragment into features
JSONFragmenter
    EXPLODE_FORMAT = JSON
    EXTRACT_ATTR = Yes
    FILEPATH_OR_URL = $(FILEPATH_OR_URL)
    JSON_QUERY = json[*][*]
    NEW_ATTRIBUTES = id level.elevation level.name speckle_type elements{}
    READ_FROM_FILE = YES
    RECURSIVE = Yes
    REJECT_EMPTY_LISTS = YES
    RESULT_ATTRIBUTE = _result
    FRAGMENTS -> PythonCaller
    FRAGMENTS -> AttributeKeeper_2
Note: Merge attributes on geometry
FeatureMerger
    ATTR_ACCUM_MODE = Merge Supplier
    ATTR_CONFLICT_RES = Use Requestor
    GEOM_TYPE = Build Aggregates
    IGNORE_NULLS = No
    JOIN_KEYS = @Value(id) @Value(id) AUTO
    MERGE_TYPE = Attributes Only
    PROCESS_DUPS = YES
    REJECT_NULL_MISSING_KEYS = No
    SUPPLIERS_FIRST = No
    MERGED -> SchemaScanner
    UNMERGED_REQUESTOR -> SchemaScanner
Note: Get schema feature for dynamic output by speckle_type
SchemaScanner
    CASE = No
    DATE_TIME_ATTRIBUTE_FORMAT = ISO
    EMPTY_ATTR_HANDLING = IGNORE
    GROUP_BY = speckle_type
    HOLD = Yes
    SCHEMA_NAME_ATTR = fme_feature_type_name
    UNBOUNDED_NUMBERS = Yes
    UNBOUNDED_STRINGS = No
    -> Speckle
    <SCHEMA> -> Schema
Speckle: Inspector
Schema: Inspector

Bookmark: Create Mesh geometry
Note: def makeGeom(feature): / # read faces and vertices from attributes / faces = feature.getAttribute('displayMesh.faces{}') / vertices = feature.getAttribute('displayMesh.vertices{}') / # create new Mesh geometry / mesh = fmeobjects.FMEMesh() / # create vertex XYZ from three vertex list entries / for i in range(int(len(vertices)/3)): / mesh.appendVertex(vertices[i*3],vertices[i*3+1],vertices[i*3+2]) / # create face from four face list vertex entries / for i in range(int(len(faces)/4)): / mesh.addMeshPart(0,[faces[i*4],faces[i*4+1],faces[i*4+2],faces[i*4+3]],None,None) / # set geometry to new Mesh / feature.setGeometry(mesh)
PythonCaller
    PYTHONSOURCE:
      import fme
      import fmeobjects


      def makeGeom(feature):
          # read faces and vertices from attributes
          faces = feature.getAttribute('displayMesh.faces{}')
          vertices = feature.getAttribute('displayMesh.vertices{}')

          # create new Mesh geometry
          mesh = fmeobjects.FMEMesh()

          # create vertex XYZ from three vertex list entries
          for i in range(int(len(vertices)/3)):
              mesh.appendVertex(vertices[i*3],vertices[i*3+1],vertices[i*3+2])

          # create face from four face list vertex entries
          for i in range(int(len(faces)/4)):
              mesh.addMeshPart(0,[faces[i*4+1],faces[i*4+2],faces[i*4+3]],None,None)

          # set geometry to new Mesh
          feature.setGeometry(mesh)
    PYTHONSYMBOL = makeGeom
    -> AttributeKeeper
AttributeKeeper
    CREATE_BULK_MODE_FEATURES = NO
    KEEP_ATTRS = level.elevation,level.name,speckle_type,id
    -> FeatureMerger [REQUESTOR]

Bookmark: Extract properties as attribute
AttributeKeeper_2
    CREATE_BULK_MODE_FEATURES = NO
    KEEP_ATTRS = id,_result
    -> AttributeRenamer_2
AttributeRenamer_2
    ATTR_TABLE = RENAME_SET_DEFAULT id > top_id
    MISSING_INPUT_ATTRS = REMOVE
    -> JSONFragmenter_4
    -> JSONFragmenter_2
    -> JSONFragmenter_3
JSONFragmenter_2
    EXPLODE_FORMAT = JSON
    EXTRACT_ATTR = Yes
    JSON_ATTR = _result
    JSON_QUERY = json["parameters"][*]
    NEW_ATTRIBUTES = name value
    READ_FROM_FILE = NO
    RECURSIVE = Yes
    REJECT_EMPTY_LISTS = YES
    FRAGMENTS -> AttributeKeeper_3
    <REJECTED> -> Junction_2
JSONFragmenter_3
    EXPLODE_FORMAT = JSON
    EXTRACT_ATTR = Yes
    JSON_ATTR = _result
    JSON_QUERY = json["level"]["parameters"][*]
    NEW_ATTRIBUTES = name value
    READ_FROM_FILE = NO
    RECURSIVE = Yes
    REJECT_EMPTY_LISTS = YES
    FRAGMENTS -> AttributeKeeper_3
    <REJECTED> -> Junction_2
Note: Break up properties into attribute name/value pairs
JSONFragmenter_4
    EXPLODE_FORMAT = JSON
    EXTRACT_ATTR = Yes
    JSON_ATTR = _result
    JSON_QUERY = json["topLevel"]["parameters"][*]
    NEW_ATTRIBUTES = name value
    READ_FROM_FILE = NO
    RECURSIVE = Yes
    REJECT_EMPTY_LISTS = YES
    FRAGMENTS -> AttributeKeeper_3
    <REJECTED> -> Junction_2
AttributeKeeper_3
    CREATE_BULK_MODE_FEATURES = NO
    KEEP_ATTRS = name,top_id,value
    -> Tester
Tester
    BOOL_OP = OR
    COMPOSITE_TEST = 1
    TEST_CLAUSE = TEST name ATTRIBUTE_HAS_A_VALUE ""
    TEST_MODE = TEST
    PASSED -> AttributeCreator
Note: Create new attribute from name/value pair
AttributeCreator
    ATTR_TABLE = SET_TO @Value(name) = @Value(value)
    -> AttributeRemover
AttributeRemover
    REMOVE_ATTRS = name,value
    -> AttributeRenamer
AttributeRenamer
    ATTR_TABLE = RENAME_SET_DEFAULT top_id > id
    MISSING_INPUT_ATTRS = REMOVE
    -> FeatureMerger [SUPPLIER]
Junction_2
