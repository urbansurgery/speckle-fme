FME workspace Sandbox-v2.fmw
Startup Python:
      import sys
      sys.path.append("/Users/jonathonbroughton/Projects/jsdbroughton/speckle-fme")

Parameters:
- PARAMETER =
- SPECKLE_ACCOUNT =

SpeckleClient_v1
    -> StreamDetails
StreamDetails: AttributeCreator
    ATTR_TABLE = SET_TO stream_url = https://speckle.xyz/streams/fd1d44405d/commits/1844b4c47c
    -> SpeckleReceiver_v1 [Speckle_URL]
SpeckleReceiver_v1
    STREAM_URL = @Value(stream_url)
SpeckleFME:Get_Default_Account_Client: PythonCreator
    NEW_ATTRIBUTES = authenticated userId userName
    PYTHONSOURCE_NEW:
      import fmeobjects

      from devtools import debug

      from specklepy.api.client import SpeckleClient
      from specklepy.api.credentials import get_default_account

      logger = fmeobjects.FMELogFile()

      class FeatureCreator(object):

          def __init__(self):

              account = get_default_account()
              client = SpeckleClient()

      #        logger.logMessageString("--------")

              client.authenticate(token=account.token)
       #       logger.logMessageString(str(client))
       #       logger.logMessageString(str(account))
        #      logger.logMessageString(str(vars(account)))
          #    logger.logMessageString(str(vars(client)))

            #  logger.logMessageString("--------")

              self.client = client
              self.account = account

              pass

          def input(self, feature):
              client = fmeobjects.FMEFeature()
              client.setAttribute(fmeobjects.kFMEFeatureTypeAttr, "SpeckleClient")
              client.setFeatureType('SpeckleClient')

              client.setAttribute("_token", self.account.token)
              client.setAttribute("_refreshToken", self.account.refreshToken)
              client.setAttribute("_host", self.client.url)

              client.setAttribute('authenticated', self.client.me is not None)
              client.setAttribute("userId", self.account.userInfo.id)
              client.setAttribute("userName", self.account.userInfo.name)


              self.pyoutput(client)



          def close(self):
              pass
    PYTHONSYMBOL = FeatureCreator
    -> Is_Authenticated
Note: Is_Authenticated [Tester] / Test Clauses: Left ValueOperatorRight Value@Value(authenticated)=YesAdvanced: / Preserve Feature Order: Per Output Port
Is_Authenticated: Tester
    BOOL_OP = OR
    COMPOSITE_TEST = 1
    TEST_CLAUSE = TEST @Value(authenticated) = Yes
    TEST_MODE = TEST
    PASSED -> SpeckleFME:Get_Streams
SpeckleFME:Get_Streams: PythonCaller
    HIDE_ATTRIBUTES = authenticated userId userName
    NEW_ATTRIBUTES = stream_id stream_name description is_public stream_no
    PYTHONSOURCE:
      import fmeobjects

      from devtools import debug

      from specklepy.api.client import SpeckleClient
      from specklepy.api.models import Stream

      logger = fmeobjects.FMELogFile()

      class FeatureProcessor(object):

          def __init__(self):
              pass

          def input(self, feature):

              logger.logMessageString('~~~~~~')


              token = feature.getAttribute('_token')
              host = feature.getAttribute('_host')

              client = SpeckleClient(host);
              client.authenticate(token)

              streams = client.stream.list()


              for x in range(len(streams)):
                    stream = streams[x]

                    logger.logMessageString(str(dir(stream)))

                    streamFeature = fmeobjects.FMEFeature()
                    streamFeature.setFeatureType('SpeckleStream')
                    streamFeature.setAttribute(fmeobjects.kFMEFeatureTypeAttr, "SpeckleStream")

                    streamFeature.setAttribute('stream_no',x)
                    streamFeature.setAttribute('stream_id',stream.id)
                    streamFeature.setAttribute('stream_name',stream.name)
                    streamFeature.setAttribute('description',stream.description)
                    streamFeature.setAttribute('is_public',stream.isPublic)

                    streamFeature.setAttribute('_token', token)
                    streamFeature.setAttribute('_host', host)

                    self.pyoutput(streamFeature)


              logger.logMessageString('~~~~~~')






          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> AttributeFilter_2
    -> SpeckleFME:Get_Branches
SpeckleFME:Get_Branches: PythonCaller
    HIDE_ATTRIBUTES = description is_public stream_no
    NEW_ATTRIBUTES = branch_id branch_name description commit_count branch_no stream_id stream_name
    PYTHONSOURCE:
      import fmeobjects

      from devtools import debug

      from specklepy.api.client import SpeckleClient
      from specklepy.api.models import Stream

      logger = fmeobjects.FMELogFile()

      class FeatureProcessor(object):

          def __init__(self):
              pass

          def input(self, feature):

              logger.logMessageString('~~~~~~')

              token = feature.getAttribute('_token')
              host = feature.getAttribute('_host')

              client = SpeckleClient(host);
              client.authenticate(token)

              streamId = feature.getAttribute('stream_id')

              stream = client.stream.get(streamId)

              if stream.branches is not None:

                  branches = stream.branches.items

                  for x in range(len(branches)):
                      branch = branches[x]

                      branchFeature = fmeobjects.FMEFeature()

                      branchFeature.setFeatureType('SpeckleBranch')
                      branchFeature.setAttribute(fmeobjects.kFMEFeatureTypeAttr, "SpeckleBranch")

                      branchFeature.setAttribute('branch_no', x)
                      branchFeature.setAttribute('branch_id', branch.id)
                      branchFeature.setAttribute('branch_name', branch.name)
                      branchFeature.setAttribute('description', branch.description)
                      branchFeature.setAttribute('commit_count', branch.commits.totalCount)

                      branchFeature.setAttribute('stream_id', stream.id)
                      branchFeature.setAttribute('stream_name', stream.name)

                      branchFeature.setAttribute('_token', token)
                      branchFeature.setAttribute('_host', host)

                      self.pyoutput(branchFeature)


                  logger.logMessageString(str(branches))


              logger.logMessageString('~~~~~~')






          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> TestFilter
Note: TestFilter [TestFilter] / Port Definitions: Test ConditionOutput PortIfTEST @Value(commit_count) > 0 / Composite Test: 1@Value(commitCount) > 0Else<All Other Conditions><Unfiltered>
TestFilter
    DEFAULT_VALUE = <UNFILTERED>
    TEST_LIST = "BOOL_OP,OR,COMPOSITE_TEST,""""""1"""""",TEST_CLAUSE,TEST @Value(commit_count) > 0",@Value(commitCount) > 0
    @Value(commitCount) > 0 -> AttributeFilter_3
AttributeFilter_3
    ATTR_NAME = branch_no
    ATTR_VALUES = <Empty>,<Missing>,<Null>,<Unfiltered>,0,1,2,3,4,5
AttributeFilter_2
    ATTR_NAME = stream_no
    ATTR_VALUES = <Empty>,<Missing>,<Null>,<Unfiltered>,0,1,2,3,4,5
    0 -> SpeckleFME:Get_Latest_From_Main
SpeckleFME:Get_Latest_From_Main: PythonCaller
    HIDE_ATTRIBUTES = stream_name
    NEW_ATTRIBUTES = stream_id branch_id commit_id object_id total_children_count
    PYTHONSOURCE:
      import fmeobjects

      from devtools import debug

      from specklepy.api import operations
      from specklepy.api.client import SpeckleClient
      from specklepy.api.client import SpeckleException
      from specklepy.api.models import Stream
      from specklepy.transports.server import ServerTransport

      import codecs

      logger = fmeobjects.FMELogFile()

      class FeatureProcessor(object):

          def __init__(self):
              pass

          def input(self, feature):

              logger.logMessageString('~~~~~~')

              token = feature.getAttribute('_token')
              host = feature.getAttribute('_host')

              client = SpeckleClient(host);
              client.authenticate(token)

              streamId = feature.getAttribute('stream_id')
              stream = client.stream.get(streamId)

              if stream.branches is None:
                  return

              branches = stream.branches.items

              main_branch = [x for x in branches if x.name == 'main'][0]

              if main_branch is None or main_branch.commits is None or main_branch.commits.cursor is None:
                  logger.logMessage(0,['No Commits on Main Branch'] , fmeobjects.FME_ERROR)
                  return

              transport = ServerTransport(client=client, stream_id=streamId)


              commit = main_branch.commits.items[0]



              objId = commit.referencedObject

              if objId is None:
                  return

              try:
                  commitObject = operations.receive(objId, transport, None)


                  logger.logMessageString('wow')

                  objectFeature = fmeobjects.FMEFeature()
                  objectFeature.setFeatureType(commitObject.speckle_type)
                  objectFeature.setAttribute(fmeobjects.kFMEFeatureTypeAttr, commitObject.speckle_type)

                  objectFeature.setAttribute('object_id', commitObject.id)
                  objectFeature.setAttribute('total_children_count', commitObject.totalChildrenCount)

                  objectFeature.setAttribute('stream_id', stream.id)
                  objectFeature.setAttribute('branch_id', main_branch.id)
                  objectFeature.setAttribute('commit_id', commit.id)

                #  objectFeature.setAttribute('data', commitObject.data)

                  logger.logMessageString(str(vars(commitObject)))


                  memberNames = commitObject.get_member_names()

                  logger.logMessageString(str(memberNames))

                  logger.logMessageString(commitObject.units)


                  self.pyoutput(objectFeature)

              except SpeckleException as e:
                  logger.logMessageString(str(dir(e)))
                  logger.logMessage(0,[e.message],fmeobjects.FME_ERROR)
                  logger.logMessage(0,[str(e.with_traceback)],fmeobjects.FME_ERROR)



              return




          def close(self):
              """This method is called once all the FME Features have been processed
              from input().
              """

              logger.logMessageString('~~~~~~')
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
GeometryFilter
    BREAK_AGG = No
    GEOM_PORT_NAMES = Point Line Arc Area Ellipse Text Raster "Point Cloud" Surface Solid Collection Null Instance

FME custom transformer SpeckleReceiver_v1

Parameters:
- STREAM_URL =

Speckle_URL (input)
    -> ProcessSpeckleCommit
ProcessSpeckleCommit: PythonCaller
    HIDE_ATTRIBUTES = stream_url
    NEW_ATTRIBUTES = fme_feature_type speckle_type object_id branch_id commit_id stream_id stream_name description commit_message
    PYTHONSOURCE = from fme_speckle.readers import StreamReader
    PYTHONSYMBOL = StreamReader
    -> AttributeFilter
AttributeFilter
    ATTR_NAME = speckle_type
    ATTR_VALUES = <Empty>,<Missing>,<Null>,<Unfiltered>,stream,branch,commit
    <UNFILTERED> -> SpeckleObjects (output)
    stream -> Stream (output)
    branch -> Branch (output)
    commit -> Commit (output)
SpeckleObjects (output)
Stream (output)
Branch (output)
Commit (output)
