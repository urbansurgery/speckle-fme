FME workspace NewDawn.fmw
Startup Python:
      import sys
      sys.path.append("D:/Repos/jsdbroughton/speckle-fme")

PythonCreator
    PYTHONSOURCE_NEW:
      import fmeobjects


      class FeatureCreator(object):
          """Template Class Interface:
          When using this class, make sure its name is set as the value of the 'Class to Process Features'
          transformer parameter.
          """

          def __init__(self):
              """Base constructor for class members."""
              pass

          def input(self, feature: fmeobjects.FMEFeature):
              """This method is called once by FME to initiate feature creation.
              Any number of features can be created and emitted by the self.pyoutput() method.
              The initial feature argument is a placeholder and can be ignored.
              """
              newFeature = fmeobjects.FMEFeature()
              self.pyoutput(newFeature)

          def close(self):
              """This method is called at the end of the class."""
              pass
    PYTHONSYMBOL = FeatureCreator
