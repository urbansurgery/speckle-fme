FME workspace Test.fmw
Startup Python:
      import sys
      sys.path.append("/Users/jonathonbroughton/Projects/jsdbroughton/speckle-fme")

Parameters:
- DestDataset_GLTF =
- DestDataset_PDF =
- SPECKLE_URL =

Writers:
- GLTF_1: GLTF to $(DestDataset_GLTF)
- PDF_1: PDF to $(DestDataset_PDF)

Creator_2
    GEOMTYPE = Geometry Object
    NUM = 10
    CREATED -> AttributeCreator_8
Note: Stream and Branch URL
AttributeCreator_8
    ATTR_TABLE:
      SET_TO group = @Evaluate(@fmod(@Value(_creation_instance),2))
      SET_TO speckle_url = FME_CONDITIONAL:DEFAULT_VALUE'https://speckle.xyz/streams/6b49ed49e5/branches/main'BOOL_OP;OR;COMPOSITE_TEST;1;TEST @Value(group) = 0'https://speckle.xyz/streams/6b49ed49e5/branches/dev'FME_NUM_CONDITIONS2___
    -> PythonCaller_2
PythonCaller_2
    GROUP_BY = speckle_url group
    HIDE_ATTRIBUTES = group
    NEW_ATTRIBUTES = REJECTED fme_feature_type
    PYTHONSOURCE = from fme_speckle.writers import StreamWriter
    PYTHONSYMBOL = StreamWriter
    -> AttributeFilter_7
AttributeFilter_7
    ATTR_NAME = fme_feature_type
    ATTR_VALUES = <Empty>,<Missing>,<Null>,<Unfiltered>,SpeckleCommit
Creator
    GEOMTYPE = Geometry Object
    NUM = 1
    CREATED -> AttributeCreator
    CREATED -> AttributeCreator_2
    CREATED -> AttributeCreator_3
    CREATED -> AttributeCreator_4
    CREATED -> AttributeCreator_5
    CREATED -> AttributeCreator_6
    CREATED -> AttributeCreator_7
AttributeCreator [off]
    ATTR_TABLE = SET_TO speckle_url = $(SPECKLE_URL)
    -> PythonCaller
AttributeCreator_2 [off]
    ATTR_TABLE = SET_TO speckle_url = https://speckle.xyz/streams/fd1d44405d/objects/80a427906336e0ef37d0d36dd02302fc
    -> PythonCaller
AttributeCreator_3 [off]
    ATTR_TABLE = SET_TO speckle_url = https://speckle.xyz/streams/fd1d44405d/objects/cc969e501281bbdb1e37453deaa3c730
    -> PythonCaller
AttributeCreator_4 [off]
    ATTR_TABLE = SET_TO speckle_url = https://speckle.xyz/streams/fd1d44405d/objects/3841e3cbc45d52c47bc2f1b7b0ad4eb9
    -> PythonCaller
AttributeCreator_5 [off]
    ATTR_TABLE = SET_TO speckle_url = https://speckle.xyz/streams/b395204656/objects/d876409ec39b1429015fd41e3424ae77
    -> PythonCaller
AttributeCreator_7
    ATTR_TABLE = SET_TO speckle_url = https://speckle.xyz/streams/fd1d44405d/objects/9c93d55cfb37415b70154f64e31b0201
    -> PythonCaller
AttributeCreator_6 [off]
    ATTR_TABLE = SET_TO speckle_url = https://speckle.xyz/streams/fd1d44405d/commits/1844b4c47c
    -> PythonCaller
    -> AttributeSplitter
PythonCaller
    HIDE_ATTRIBUTES = _creation_instance speckle_url
    NEW_ATTRIBUTES = speckle_type, REJECTED
    PYTHONSOURCE = from fme_speckle.readers import StreamReader
    PYTHONSYMBOL = StreamReader
    -> AttributeFilter
AttributeFilter
    ATTR_NAME = speckle_type
    ATTR_VALUES = <Empty>,<Missing>,<Null>,<Unfiltered>,commit,branch,stream
    <UNFILTERED> -> AttributeExposer
AttributeExposer
    ATTR_LIST = id,parent_id,speckle_type,category
    -> House (writer GLTF_1)
    -> Layer1 (writer PDF_1)
    -> AttributeExposer_2
    -> AttributeFilter_2
    -> UniqueValueLogger
    -> AttributeFilter_5
House (writer GLTF_1) [off]
AttributeFilter_2 [off]
    ATTR_NAME = parent_id
    ATTR_VALUES = <Empty>,<Missing>,<Null>,<Unfiltered>
    <UNFILTERED> -> AttributeFilter_3
    <UNFILTERED> -> AttributeFilter_4
    <UNFILTERED> -> Aggregator
AttributeFilter_3 [off]
    ATTR_NAME = speckle_type
    ATTR_VALUES = <Empty>,<Missing>,<Null>,<Unfiltered>,Base
AttributeFilter_4 [off]
    ATTR_NAME = id
    ATTR_VALUES = <Empty>,<Missing>,<Null>,<Unfiltered>,fb6a4ec711073b4f91871b3562f790d8,a9e42ded91a1733d7adf71fd17a28c56,56646ea75c052785252d7853ff7d6deb
Aggregator [off]
    ACCUM_ATTRS_NAME = Drop Incoming Attributes
    AGGREGATE_TYPE = Homogeneous Collection (If Possible)
    GROUP_BY = parent_id
    MODE = Geometry - Assemble One Level
    SEP = ,
    AGGREGATE -> Deaggregator_2
Deaggregator_2 [off]
    COPY_ATTR = Every Node
    EXPLODE_INSTANCES = No
    ID_ATTR = _hierarchy_id
    ID_SELECTION = ID and Parent ID
    LIST_ATTR_MODE_LOOKUP = LEAN
    MODE = Preserve Hierarchy
    PARENT_ID_ATTR = _hierarchy_parent_id
    SPLIT_COMPOSITES = No
Layer1 (writer PDF_1) [off]
    attributes: speckle_type, string, REJECTED string, id string, parent_id string, speckle_type string, category string
AttributeExposer_2 [off]
    ATTR_LIST = @<Room␣Separation>
    -> AttributeKeeper
AttributeKeeper [off]
    CREATE_BULK_MODE_FEATURES = No
UniqueValueLogger [off]
    VAL = @Value(id)
    -> Counter
Counter [off]
    CNT_ATTR = _hierarchy_id
    SCOPE = Local
    START = 0
AttributeFilter_5
    ATTR_NAME = speckle_type
    ATTR_VALUES = <Empty>,<Missing>,<Null>,<Unfiltered>,Objects.BuiltElements.Topography:Objects.BuiltElements.Revit.RevitTopography,Objects.Geometry.Line,Objects.BuiltElements.Ceiling:Objects.BuiltElements.Revit.RevitCeiling,Objects.BuiltElements.Revit.FamilyInstance,Objects.BuiltElements.Revit.RevitElement,Objects.BuiltElements.Column:Objects.BuiltElements.Revit.RevitColumn,Objects.BuiltElements.Roof:Objects.BuiltElements.Revit.RevitRoof.RevitRoof:Objects.BuiltElements.Revit.RevitRoof.RevitExtrusionRoof,Base,Objects.BuiltElements.Roof:Objects.BuiltElements.Revit.RevitRoof.RevitRoof:Objects.BuiltElements.Revit.RevitRoof.RevitFootprintRoof,Objects.BuiltElements.Wall:Objects.BuiltElements.Revit.RevitWall,Objects.BuiltElements.Opening:Objects.BuiltElements.Revit.RevitOpening:Objects.BuiltElements.Revit.RevitWallOpening,Objects.BuiltElements.Revit.RevitRailing,Objects.BuiltElements.Revit.BuildingPad,Objects.BuiltElements.Revit.RevitStairRun,Objects.BuiltElements.Revit.RevitStair,Objects.BuiltElements.Revit.RevitStairLanding,Objects.BuiltElements.Floor:Objects.BuiltElements.Revit.RevitFloor,Objects.BuiltElements.Revit.Curve.RoomBoundaryLine
    Objects.BuiltElements.Revit.FamilyInstance -> AttributeFilter_6
AttributeFilter_6
    ATTR_NAME = category
    ATTR_VALUES = <Empty>,<Missing>,<Null>,<Unfiltered>,Casework,Ceilings,Columns,Curtain Panels,Curtain Wall Mullions,Doors,Entourage,Generic Models,Floors,Furniture,Lighting Fixtures,Planting,Plumbing Fixtures,Railings,Roofs,Rooms,Specialty Equipment,Stairs,Structural Columns,Structural Framing,Walls,Windows,Electrical Equipment,Structural Foundations,Site,Furniture Systems
AttributeSplitter [off]
    ATTR_NAME = speckle_url
    DELIMITER = /
    DROP_EMPTY_PARTS = No
    LIST_NAME = _list
    TRIM_OPTION = Both

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =

Input (input)
    -> AttributeCreator

Bookmark: Count unique attribute values
AttributeCreator
    ATTR_TABLE = SET_TO _value = $(VAL)
    -> AttributeKeeper
Note: Remove unwanted / attributes
AttributeKeeper
    CREATE_BULK_MODE_FEATURES = No
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
